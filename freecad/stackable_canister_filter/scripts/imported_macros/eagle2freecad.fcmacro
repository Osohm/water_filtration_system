#########################################################################################
#This software is licenced under CC-BY (http://creativecommons.org/licenses/by/3.0/) 
#but feel free to donate  to the Open Source Hardware Foundation (http://www.oshwa.org/)
#if you want to pay something for the usage of this software.
#########################################################################################

import Part
from FreeCAD import Base
import csv
import FreeCAD, FreeCADGui, Part
import math
from PyQt4 import QtGui
from PyQt4 import QtCore
import os
import string


eagle_dimension_layer = 20
setting_cut_holes = False


try:
    import xml.etree.cElementTree as ET
except ImportError:
    import xml.etree.ElementTree as ET


def getElementByPathAndAttrib(elem, path, name, value):
  for e in elem.findall(path):
    if e.attrib.get(name)==value:
      return e;

#get total Height of PCB
def getPCBThickness(element):
  totalHeight = 0

  #get design rule for copper thickness and parse it in array
  layerThicknesses = getElementByPathAndAttrib(drawing, "board/designrules/param", "name", "mtCopper")
  layerThicknesses = layerThicknesses.attrib['value'];
  layerThicknesses = layerThicknesses.translate(None, string.letters).split(' ')

  #get design rule for isolation layer (i.e. FR4) thickness and parse it in array
  layerSpacings    = getElementByPathAndAttrib(drawing, 'board/designrules/param', 'name',"mtIsolate")
  layerSpacings    = layerSpacings.attrib['value']
  layerSpacings    = layerSpacings.translate(None, string.letters).split(' ')

  #get design rule for layer setup and parse it
  layerSetup       = getElementByPathAndAttrib(drawing, 'board/designrules/param', 'name',"layerSetup")
  layerSetup       = layerSetup.attrib['value']
  layerSetup       = layerSetup.replace('*',' ').replace('+',' ')
  layerSetup       = layerSetup.replace('(', ' ').replace(')',' ').strip().split(' ')

  #find [t:...:b] syntax and remove the t and b parameters, as we do not need them 
  #to calculate the thickness of the pcb
  newLayerSetup = []
  for layer in layerSetup:
    if layer[0]=='[':
      layer_array = layer.split(':')
      if len(layer_array) == 2:
        layer = layer_array[1]
      else:
        layer = layer.replace('[','')
    if layer[-1]==']':
      layer_array = layer.split(':')
      if len(layer_array) == 2:
        layer = layer_array[0]
      else:
        layer = layer.replace(']','')
    newLayerSetup.append(layer)
  layerSetup = newLayerSetup


  #loop through layer setup and sum up all thicknesses for copper and isolation
  lastLayer        = -1
  for layer in layerSetup:
    if not layer=='':
      #print "Layer: ", layer
      #print "adding thickness of layer: ", layerThicknesses[int(layer)-1]
      totalHeight += float(layerThicknesses[int(layer)-1])
      if (lastLayer >= 0):
        #print "adding thickness of spacing: ", layerSpacings[int(lastLayer)-1]
        totalHeight += float(layerSpacings[int(lastLayer)-1])
      lastLayer = layer
  return totalHeight


def getAngle(x1,y1,x2,y2):
  x_diff = x2-x1
  y_diff = y2-y1
  
  if x_diff != 0:
    angle = math.degrees(math.atan(y_diff / x_diff))
  else:
    angle = 90
  
  if (x2 < x1):
    angle += 180
  elif (x2==x1 and y2<y1):
    angle += 180
  
  return angle

def getCurvedLine(x1,y1,x2,y2,curve):
#middle between start and end point
  x_mid = (x1 + x2) / 2
  y_mid = (y1 + y2) / 2

  #difference between the points to calculate the angle of the direct line
  angle = getAngle(x1,y1,x2,y2)


  #add angle between mid and center points which is 90 degrees
  angle += 90
  
  #distance from point 1 to the middle point
  dist_1_mid = ((x1-x_mid)**2 + (y1-y_mid)**2)**0.5

  #distance from the middle point to the center of the circle
  dist_mid_center = dist_1_mid / math.tan(math.radians(curve/2))

  x_center = x_mid + dist_mid_center * math.cos(math.radians(angle))
  y_center = y_mid + dist_mid_center * math.sin(math.radians(angle))

  radius = ( (x_center - x1)**2 + (y_center - y1)**2)**0.5

  #get angle from center to middle point
  #but only if they are different
  if not (x_center == x_mid and y_center == y_mid):
    angle = getAngle(x_center, y_center, x_mid, y_mid)

  #point 3 that is the last missing point to draw an arc
  x3 = x_center + radius * math.cos(math.radians(angle))
  y3 = y_center + radius * math.sin(math.radians(angle))

  arc = Part.Arc(Base.Vector(x1,y1,0),Base.Vector(x3,y3,0),Base.Vector(x2,y2,0))
  
  return arc

def getLine(elem):
  #TODO: change to commented code line - this will cause other parts of the source to fail: investigate it ;)
  #if ('curve' not in elem.attrib):
  if ('curve' not in elem):
    return Part.makeLine((elem.attrib['x1'], elem.attrib['y1'],0), (elem.attrib['x2'],elem.attrib['y2'],0))
  else:
    return Part.Edge(getCurvedLine(float(elem.attrib['x1']), float(elem.attrib['y1']),float(elem.attrib['x2']), float(elem.attrib['y2']), float(elem.attrib['curve'])))

def getEdgeByParams(x1,y1,x2,y2,curve):
  if (curve == 0):
    return Part.makeLine((x1, y1,0), (x2,y2,0))
  else:
    return Part.Edge(getCurvedLine(x1, y1,x2, y2, curve))


def getPlacedModel(part, model,height):
    useAttributeForPosition = False
    
    p = model.copy()
    
    angle = getElementByPathAndAttrib(elem,'attribute','name',"ANGLE")
    if (angle != None):
      #print "#"
      angle = angle.attrib['value'].split(',')
      angle = float(angle[0])
      axis = getElementByPathAndAttrib(elem,'attribute','name',"AXIS")
      if (axis != None):
        #print "#"
        axis = axis.attrib['value'].split(',')
        axis = Base.Vector(float(axis[0]),float(axis[1]),float(axis[2]))
        position = getElementByPathAndAttrib(elem,'attribute','name',"POSITION")
        if (position != None):        
          #print "#"
          position = position.attrib['value'].split(',')
          position = Base.Vector(float(position[0]),float(position[1]),float(position[2]))
          if (not angle == 0):
            p.rotate(Base.Vector(0,0,0), axis, angle)
          print "done rotation"
          p.translate(position)
          print "done position"
          useAttributeForPosition = True
          #print "##################################################################################"
    #else:
      #print angle
    
    if (useAttributeForPosition == False):
      if 'rot' in part.attrib:
        rot = float(part.attrib['rot'].translate(None, string.letters))
        mirror = part.attrib['rot'].translate(None, string.digits)
      else:
        rot = 0
        mirror='R'
      
      p.translate(Base.Vector(0,0,height / 2))
      
      p.rotate(Base.Vector(0,0,0),Base.Vector(0,0,1),rot)
      mirrorMultiplicator = 1
      if (mirror[0] == 'M'):
        p.rotate(Base.Vector(0,0,0), Base.Vector(0,1,0), 180)
        mirrorMultiplicator = -1
      p.translate(Base.Vector(float(part.attrib['x']),float(part.attrib['y']),0))
      #print "--------------------------------------------------------------------------------------"
    
    returnVal = {}
    returnVal['part'] = p
    returnVal['usedAttrib'] = useAttributeForPosition
    return returnVal

def getWireFromPolygon(elem):
  millwire = []
  lastPoint = ''
  firstPoint = ''
  curve = 0
  for elem2 in elem.findall('vertex'):
    nextPoint = Base.Vector(float(elem2.attrib['x']),float(elem2.attrib['y']),0)
    if (lastPoint == ''):
      firstPoint = nextPoint
    else:
      millwire.append(getEdgeByParams(lastPoint[0], lastPoint[1], nextPoint[0], nextPoint[1], curve))
    curve = 0
    if 'curve' in elem2.attrib:
      curve = float(elem2.attrib['curve'])

    lastPoint = nextPoint
  millwire.append(getEdgeByParams(lastPoint[0], lastPoint[1], firstPoint[0], firstPoint[1], curve))
    
  return Part.Wire(millwire)



libFolder = ''
filename = ''
libFolder = str(QtGui.QFileDialog.getExistingDirectory(None, "Select Directory for Libraries"))
filename = str(QtGui.QFileDialog.getOpenFileName(None, 'Open Eagle Board file',''))


holes = []
parts = []
freeParts = []
edges = []
PCBs = []
milling = []
packages = {}
missingpackages = {}

milledVolumes = []

tree = ET.ElementTree(file=filename)
root = tree.getroot()
drawing = root[0]
dimensionLibrary = {}
drillLibrary = {}
millingLibrary = {}
milledVolumesLibrary = {}

totalHeight = getPCBThickness(drawing)

#find lines that make up the dimensions of pcbs directly
for elem in drawing.findall('board/plain/wire'):
  if elem.attrib['layer']==str(eagle_dimension_layer):
    edges.append(getLine(elem));

#find lines that make up the milling of pcbs directly
for elem in drawing.findall('board/plain/wire'):
  if elem.attrib['layer']=="46":
    milling.append(getLine(elem));
    
#find vias
for elem in drawing.findall('board/signals/signal/via'):
  holes.append(Part.makeCylinder(float(elem.attrib['drill'])/2,totalHeight,Base.Vector(float(elem.attrib['x']),float(elem.attrib['y']),-totalHeight/2)))


#find parts that contain dimension lines or holes or millings
for elem in drawing.findall('board/libraries/library'):
  library = elem.attrib['name']
  for elem2 in elem.findall('packages/package'):
    part = elem2.attrib['name']
    for elem3 in elem2.findall('wire'):
      if elem3.attrib["layer"]=="20":
        if library not in dimensionLibrary:
          dimensionLibrary[library] = {}
        if part not in dimensionLibrary[library]:
          dimensionLibrary[library][part] = []
        dimensionLibrary[library][part].append(getLine(elem3))
    for elem3 in elem2.findall('wire'):
      if elem3.attrib['layer']=="46":
        if library not in millingLibrary:
          millingLibrary[library] = {}
        if part not in millingLibrary[library]:
          millingLibrary[library][part] = []
        millingLibrary[library][part].append(getLine(elem3))
    for elem3 in elem2.findall('hole'):
      if library not in drillLibrary:
        drillLibrary[library] = {}
      if part not in drillLibrary[library]:
        drillLibrary[library][part] = []
      drillLibrary[library][part].append(Part.makeCylinder(float(elem3.attrib['drill'])/2,totalHeight,Base.Vector(float(elem3.attrib['x']),float(elem3.attrib['y']),-totalHeight/2)))
    for elem3 in elem2.findall('pad'):
      if library not in drillLibrary:
        drillLibrary[library] = {}
      if part not in drillLibrary[library]:
        drillLibrary[library][part] = []
      drillLibrary[library][part].append(Part.makeCylinder(float(elem3.attrib['drill'])/2,totalHeight,Base.Vector(float(elem3.attrib['x']),float(elem3.attrib['y']),-totalHeight/2)))

    for elem3 in elem2.findall('polygon'):
      if elem3.attrib["layer"]=="46":
        if library not in milledVolumesLibrary:
          milledVolumesLibrary[library] = {}
        if part not in milledVolumesLibrary[library]:
          milledVolumesLibrary[library][part] = []
        millwire = getWireFromPolygon(elem3)
        millwire = Part.Face(millwire)
        millwire.translate(Base.Vector(0,0,-totalHeight/2))
        milledVolumesLibrary[library][part].append(millwire.extrude(Base.Vector(0,0,totalHeight)))



for elem in drawing.findall('board/elements/element'):
  #use parts from library to finish list of dimensions
  if elem.attrib['library'] in dimensionLibrary and elem.attrib['package'] in dimensionLibrary[elem.attrib['library']]:
    for elem2 in dimensionLibrary[elem.attrib['library']][elem.attrib['package']]:
      dimensionLineCpy = getPlacedModel(elem, elem2,0)['part']
      edges.append(dimensionLineCpy)
  #use parts from library to finish list of millings
  if elem.attrib['library'] in millingLibrary and elem.attrib['package'] in millingLibrary[elem.attrib['library']]:
    for elem2 in millingLibrary[elem.attrib['library']][elem.attrib['package']]:
      millingLineCpy = getPlacedModel(elem, elem2,0)['part']
      milling.append(millingLineCpy)
  if elem.attrib['library'] in milledVolumesLibrary and elem.attrib['package'] in milledVolumesLibrary[elem.attrib['library']]:
    for elem2 in milledVolumesLibrary[elem.attrib['library']][elem.attrib['package']]:
      milledVolume = getPlacedModel(elem, elem2,0)['part']
      milledVolumes.append(milledVolume)
  if elem.attrib['library'] in drillLibrary and elem.attrib['package'] in drillLibrary[elem.attrib['library']]:
    for elem2 in drillLibrary[elem.attrib['library']][elem.attrib['package']]:
      hole = getPlacedModel(elem, elem2,0)['part']
      holes.append(hole)
  
  #collect used footprints
  footprint = elem.attrib['package']
  for attribute in elem.findall('attribute'):
    if attribute.attrib['name']=="STEP":
      footprint = attribute.attrib['value']
  packages[footprint] = ''

#look for files with ending .stp or .step and import the models
#if the packages are used on the pcb
#TODO: add support for importing more than step models (freecad supports more natively)
for dirname, dirnames, filenames in os.walk(libFolder):
  for filename in filenames:
      file = filename.split('.') #attention: files might have more than one dot in their name
      if (file[len(file)-1]=='stp' or file[len(file)-1]=='step'):
        ending = file.pop(len(file)-1) #remove fileending (.stp or .step)
        file = ".".join(file)
        if (file in packages):
          packages[file] = Part.read(os.path.join(dirname, filename))


#insert parts in drawing using the already imported packages
for elem in drawing.findall('board/elements/element'):
  footprint = elem.attrib['package']
  for attribute in elem.findall('attribute'):
    if attribute.attrib['name']=="STEP":
      footprint = attribute.attrib['value']
  if (packages[footprint] == '' and footprint not in missingpackages):
    print "missing package ", footprint
    missingpackages[footprint] = 'reported'
  elif packages[footprint] != '':
    p = getPlacedModel(elem, packages[footprint], totalHeight)
    if (p['usedAttrib']==False):
      parts.append(p['part'])
    else:
      freeParts.append(p['part'])


#sort edges to form a single closed 2D shape
loopcounter = 0

if (not len(edges)>0):
  print "no PCBs found, are you using layer "+str(eagle_dimension_layer)+" for your dimensions?"
else:
  newEdges = [];
  newEdges.append(edges.pop(0))
  nextCoordinate = newEdges[0].Curve.EndPoint
  firstCoordinate = newEdges[0].Curve.StartPoint
  while(len(edges)>0 and loopcounter < 2):
    loopcounter = loopcounter + 1
    #print "nextCoordinate: ", nextCoordinate
    for j, edge in enumerate(edges):
      #print "compare to: ", edges[j].Curve.StartPoint, "/" , edges[j].Curve.EndPoint
      if edges[j].Curve.StartPoint == nextCoordinate:
        nextCoordinate = edges[j].Curve.EndPoint
        newEdges.append(edges.pop(j))
        loopcounter = 0
        break
      elif edges[j].Curve.EndPoint == nextCoordinate:
        nextCoordinate = edges[j].Curve.StartPoint
        newEdges.append(edges.pop(j))
        loopcounter = 0
        break
    if nextCoordinate == firstCoordinate:
      newEdges = Part.Wire(newEdges)
      newEdges = Part.Face(newEdges)
      newEdges.translate(Base.Vector(0,0,-totalHeight/2))
      newEdges = newEdges.extrude(Base.Vector(0,0,totalHeight))
      PCBs.append(newEdges)
      if (len(edges)>0):
        newEdges = [];
        newEdges.append(edges.pop(0))
        nextCoordinate = newEdges[0].Curve.EndPoint
        firstCoordinate = newEdges[0].Curve.StartPoint

  if loopcounter == 2:
    print "*** omitting PCBs because there was a not closed loop in your dimension lines ***"
    print "*** have a look at position x=" + str(nextCoordinate.x) + "mm, y=" + str(nextCoordinate.y) + "mm ***"



  #sort millings to form a single closed 2D shape
  loopcounter = 0

  if not milling==[]:
    newMilling = [];
    newMilling.append(milling.pop(0))
    nextCoordinate = newMilling[0].Curve.EndPoint
    firstCoordinate = newMilling[0].Curve.StartPoint
    while(len(milling)>0 and loopcounter < 2):
      loopcounter = loopcounter + 1
      #print "nextCoordinate: ", nextCoordinate
      for j, edge in enumerate(milling):
        #print "compare to: ", milling[j].Curve.StartPoint, "/" , milling[j].Curve.EndPoint
        if milling[j].Curve.StartPoint == nextCoordinate:
          loopcounter = 0
          nextCoordinate = milling[j].Curve.EndPoint
          newMilling.append(milling.pop(j))
        elif milling[j].Curve.EndPoint == nextCoordinate:
          loopcounter = 0
          nextCoordinate = milling[j].Curve.StartPoint
          newMilling.append(milling.pop(j))
      if nextCoordinate == firstCoordinate:
        newMilling = Part.Wire(newMilling)
        newMilling = Part.Face(newMilling)
        newMilling.translate(Base.Vector(0,0,-totalHeight/2))
        milledVolumes.append(newMilling.extrude(Base.Vector(0,0,totalHeight)))
        if (len(milling)>0):
          newMilling = [];
          newMilling.append(milling.pop(0))
          nextCoordinate = newMilling[0].Curve.EndPoint
          firstCoordinate = newMilling[0].Curve.StartPoint

  if loopcounter == 2:
    print "*** omitting some millings because there was a not closed loop in your milling lines ***"
    print "*** have a look at position x=" + str(nextCoordinate.x) + "mm, y=" + str(nextCoordinate.y) + "mm ***"

  for extruded in PCBs:
    #search for orientation of each pcb in 3d space, save it (no transformation yet!)
    angle = 0;
    axis = Base.Vector(0,0,1)
    position = Base.Vector(0,0,0)
    
    for elem in drawing.findall('board/plain/text'):
      if elem.attrib['layer']=="223":
        if extruded.isInside(Base.Vector(float(elem.attrib['x']),float(elem.attrib['y']),0), 0.000001, True):
         #print "found $text"
          keyValue = elem.text.split('=')
          if keyValue[0] == "angle":
            angle = float(keyValue[1])
           #print "found angle"
          if keyValue[0] == "axis":
            splitValue = keyValue[1].split(',')
            axis = Base.Vector(float(splitValue[0]),float(splitValue[1]),float(splitValue[2]))
           #print "found axis"
          if keyValue[0] == "position":
            splitValue = keyValue[1].split(',')
            position = Base.Vector(float(splitValue[0]),float(splitValue[1]),float(splitValue[2]))
           #print "found position"
    
    #remove milled areas of the pcb
    for milledVolume in milledVolumes:
      extruded = extruded.cut(milledVolume)


    #find parts on this pcb (actually IN the PCB) and perform translation and rotation as for the pcb
    parts_for_fuse = []
    for part in parts:
      if extruded.isInside(part.Placement.Base, 0.000001, True):
		part.rotate(Base.Vector(0,0,0), axis, angle)
		part.translate(position)		
        #part.nullify()

    #cut out all drilled holes
    if setting_cut_holes==True:
      for hole in holes:
        extruded = extruded.cut(hole)


    #now when the pcb if fully populated perform transformations to align it correctly in 3d space
    extruded.rotate(Base.Vector(0,0,0), axis, angle)
    extruded.translate(position)
    #display the part
    Part.show(extruded)

  for part in parts:
    if not part.isNull():
      Part.show(part)

  for part in freeParts:
    Part.show(part)
